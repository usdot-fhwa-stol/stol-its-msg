BasicSafetyMessage DEFINITIONS AUTOMATIC TAGS ::= BEGIN
MessageFrame ::= SEQUENCE {
    messageId DSRCmsgID,
    value BasicSafetyMessage
}

REG-EXT-ID-AND-TYPE ::= CLASS {
   &id     RegionId UNIQUE,
   &Type
   } WITH SYNTAX {&Type IDENTIFIED BY &id}

PARTII-EXT-ID-AND-TYPE ::= CLASS {
   &id     PartII-Id UNIQUE,
   &Type
   } WITH SYNTAX {&Type IDENTIFIED BY &id}

RegionId ::= INTEGER (0..255)

PartII-Id ::= INTEGER (0..63)

vehicleSafetyExt       PartII-Id ::= 0  -- VehicleSafetyExtensions
specialVehicleExt      PartII-Id ::= 1  -- SpecialVehicleExtensions
supplementalVehicleExt PartII-Id ::= 2  -- SupplementalVehicleExtensions
-- NOTE: new registered Part II content IDs will be denoted here

-- In a given message there may be multiple extensions present 
-- but at most one instance of each extension type.
BSMpartIIExtension  PARTII-EXT-ID-AND-TYPE ::= { 
   { VehicleSafetyExtensions       IDENTIFIED BY vehicleSafetyExt} |
   { SpecialVehicleExtensions      IDENTIFIED BY specialVehicleExt} |
   { SupplementalVehicleExtensions IDENTIFIED BY supplementalVehicleExt} ,
   ... 
   } 

BasicSafetyMessage ::= SEQUENCE {
   coreData      BSMcoreData,   
   partII        SEQUENCE (SIZE(1..8)) OF 
                 PartIIcontent {{ BSMpartIIExtension }} OPTIONAL,
   regional      SEQUENCE (SIZE(1..4)) OF 
                 RegionalExtension {{Reg-BasicSafetyMessage}} OPTIONAL
   }

  

MsgCount ::= INTEGER (0..127)
DSRCmsgID ::= INTEGER (0..127)
VehicleClassification ::= SEQUENCE {
   keyType         BasicVehicleClass OPTIONAL,
   role            BasicVehicleRole OPTIONAL, 
   iso3883         Iso3833VehicleType OPTIONAL,
   hpmsType        VehicleType OPTIONAL,  
   vehicleType     VehicleGroupAffected OPTIONAL,      
   responseEquip   IncidentResponseEquipment OPTIONAL, 
   responderType   ResponderGroupAffected OPTIONAL,    
   fuelType        FuelType OPTIONAL,      
   regional        SEQUENCE (SIZE(1..4)) OF 
                   RegionalExtension {{Reg-VehicleClassification}} OPTIONAL
   }

WiperSet ::= SEQUENCE {
   statusFront    WiperStatus,
   rateFront      WiperRate,
   statusRear     WiperStatus      OPTIONAL,
   rateRear       WiperRate        OPTIONAL
   }   

SemiMajorAxisOrientation ::= INTEGER (0..65535)

VehicleMass ::= INTEGER (0..255)

DisabledVehicle ::= SEQUENCE {
   statusDetails     ITIScodes (523..541),   
   locationDetails   GenericLocations   OPTIONAL 
   }

AntiLockBrakeStatus ::= ENUMERATED {
   unavailable (0), 
   off         (1), 
   on          (2), 
   engaged     (3)  
   }

VehicleLength ::= INTEGER (0.. 4095) 

TrailerMass ::= INTEGER (0..255) 

Node-XY-24b ::= SEQUENCE {
   x  Offset-B12,
   y  Offset-B12
   }

SirenInUse ::= ENUMERATED {
     unavailable   (0), 
     notInUse      (1),  
     inUse         (2),  
     reserved      (3)  
     }

Longitude ::= INTEGER (-1799999999..1800000001)  

IsDolly ::= BOOLEAN 

Offset-B12 ::= INTEGER (-2048..2047)

TemporaryID ::= OCTET STRING (SIZE(4))

PositionConfidence ::= ENUMERATED {
   unavailable (0),  
   a500m   (1), 
   a200m   (2), 
   a100m   (3), 
   a50m    (4), 
   a20m    (5), 
   a10m    (6), 
   a5m     (7), 
   a2m     (8), 
   a1m     (9), 
   a50cm  (10), 
   a20cm  (11), 
   a10cm  (12), 
   a5cm   (13), 
   a2cm   (14), 
   a1cm   (15)  
   } 

BasicVehicleClass ::= INTEGER (0..255)

DMinute ::= INTEGER (0..60) 

PositionConfidenceSet ::= SEQUENCE {
   pos        PositionConfidence, 
   elevation  ElevationConfidence 
   }

Iso3833VehicleType ::= INTEGER (0..100) 

HeadingSlice ::= BIT STRING {
   from000-0to022-5degrees  (0),   
   from022-5to045-0degrees  (1),   
   from045-0to067-5degrees  (2),   
   from067-5to090-0degrees  (3),   
   from090-0to112-5degrees  (4),   
   from112-5to135-0degrees  (5),   
   from135-0to157-5degrees  (6),   
   from157-5to180-0degrees  (7),   
   from180-0to202-5degrees  (8),   
   from202-5to225-0degrees  (9),   
   from225-0to247-5degrees  (10),  
   from247-5to270-0degrees  (11),  
   from270-0to292-5degrees  (12),  
   from292-5to315-0degrees  (13),  
   from315-0to337-5degrees  (14),  
   from337-5to360-0degrees  (15)  
   }  (SIZE (16))

ObstacleDirection ::= Angle

Reg-VehicleClassification REG-EXT-ID-AND-TYPE ::= { ...  }

VehicleSafetyExtensions ::= SEQUENCE {
   events             VehicleEventFlags OPTIONAL,
   pathHistory        PathHistory       OPTIONAL, 
   pathPrediction     PathPrediction    OPTIONAL,
   lights             ExteriorLights    OPTIONAL                       
   }

DOffset ::= INTEGER (-840..840) 

SemiMajorAxisAccuracy ::= INTEGER (0..255)

ElevationConfidence ::= ENUMERATED {
   unavailable (0),  
   elev-500-00 (1),  
   elev-200-00 (2),  
   elev-100-00 (3),  
   elev-050-00 (4),  
   elev-020-00 (5),  
   elev-010-00 (6),  
   elev-005-00 (7),  
   elev-002-00 (8),  
   elev-001-00 (9),  
   elev-000-50 (10), 
   elev-000-20 (11), 
   elev-000-10 (12), 
   elev-000-05 (13), 
   elev-000-02 (14), 
   elev-000-01 (15)  
   }  

EssSolarRadiation ::= INTEGER (0..65535) 

EssMobileFriction ::= INTEGER (0..101)

VertOffset-B12 ::= INTEGER (-2048..2047)  

PathHistory ::= SEQUENCE {
   initialPosition  FullPositionVector    OPTIONAL,
   currGNSSstatus   GNSSstatus            OPTIONAL,   
   crumbData  	    PathHistoryPointList
   }

AmbientAirPressure ::= INTEGER (0..255) 

DSecond ::= INTEGER (0..65535) 

Acceleration ::= INTEGER (-2000..2001) 

CoarseHeading ::= INTEGER (0..240)

SpeedConfidence ::= ENUMERATED {
   unavailable (0), 
   prec100ms   (1), 
   prec10ms    (2), 
   prec5ms     (3), 
   prec1ms     (4), 
   prec0-1ms   (5), 
   prec0-05ms  (6), 
   prec0-01ms  (7)  
   }

PartIIcontent  { PARTII-EXT-ID-AND-TYPE: Set} ::= SEQUENCE {
   partII-Id     PARTII-EXT-ID-AND-TYPE.&id( {Set} ),
   partII-Value  PARTII-EXT-ID-AND-TYPE.&Type( {Set}{@partII-Id} )
   }

EmergencyDetails ::= SEQUENCE {
   sspRights    SSPindex, 
   sirenUse     SirenInUse,                 
   lightsUse    LightbarInUse,              
   multi        MultiVehicleResponse,
   events       PrivilegedEvents OPTIONAL,
   responseType ResponseType OPTIONAL
   }

   

Angle ::= INTEGER (0..28800) 

VertOffset-B07 ::= INTEGER (-64..63)  

TrailerData ::= SEQUENCE {
   sspRights   SSPindex, 
   connection  PivotPointDescription,
   units       TrailerUnitDescriptionList
   }

ITIScodes ::= INTEGER (0..65535)

PathHistoryPointList ::= SEQUENCE (SIZE(1..23)) OF PathHistoryPoint

Confidence ::= INTEGER (0..200)

RTCMmessage ::= OCTET STRING (SIZE(1..1023))

GrossSpeed ::= INTEGER (0..31) 

TrailerUnitDescription ::= SEQUENCE {
   isDolly          IsDolly, 
   width            VehicleWidth,   
   length           VehicleLength,  
   height           VehicleHeight OPTIONAL,
   mass             TrailerMass   OPTIONAL,
   bumperHeights    BumperHeights OPTIONAL,
   centerOfGravity  VehicleHeight OPTIONAL,
   frontPivot       PivotPointDescription,
   rearPivot        PivotPointDescription OPTIONAL,
   rearWheelOffset  Offset-B12 OPTIONAL,   
   positionOffset   Node-XY-24b, 
   elevationOffset  VertOffset-B07 OPTIONAL,   
   crumbData  	    TrailerHistoryPointList OPTIONAL 
   }

EssPrecipYesNo ::= ENUMERATED {precip (1), noPrecip (2), error (3)} 

ThrottleConfidence ::= ENUMERATED {
   unavailable     (0), 
   prec10percent   (1), 
   prec1percent    (2), 
   prec0-5percent  (3)  
   }

Reg-SupplementalVehicleExtensions REG-EXT-ID-AND-TYPE ::= { ...  }

TransmissionState ::= ENUMERATED {
   neutral      (0), 
   park         (1), 
   forwardGears (2), 
   reverseGears (3), 
   reserved1    (4),      
   reserved2    (5),      
   reserved3    (6),      
   unavailable  (7)  
   }

Elevation ::= INTEGER (-4096..61439) 

SemiMinorAxisAccuracy ::= INTEGER (0..255)

AuxiliaryBrakeStatus ::= ENUMERATED {
   unavailable (0), 
   off         (1), 
   on          (2), 
   reserved    (3)  
   }

PathHistoryPoint ::= SEQUENCE {
   latOffset       OffsetLL-B18,
   lonOffset       OffsetLL-B18,
   elevationOffset VertOffset-B12,  
   timeOffset      TimeOffset,
   speed           Speed                 OPTIONAL, 
   posAccuracy     PositionalAccuracy    OPTIONAL, 
   heading         CoarseHeading         OPTIONAL 
   }

PivotingAllowed ::= BOOLEAN 

YawRate ::= INTEGER (-32767..32767) 



SteeringWheelAngle ::= INTEGER (-126..127) 

SpecialVehicleExtensions ::= SEQUENCE {
   vehicleAlerts  EmergencyDetails OPTIONAL,
   description    EventDescription  OPTIONAL, 
   trailers       TrailerData OPTIONAL
   }

SSPindex ::= INTEGER (0..31)

ObstacleDetection ::= SEQUENCE {  
   obDist          ObstacleDistance,        
   obDirect        ObstacleDirection,       
   description     ITIScodes (523..541) OPTIONAL, 
   locationDetails GenericLocations OPTIONAL,        
   dateTime        DDateTime,               
   vertEvent       VerticalAccelerationThreshold OPTIONAL 
   }

TractionControlStatus ::= ENUMERATED {
   unavailable (0), 
   off         (1), 
   on          (2), 
   engaged     (3)  
   }

BrakeSystemStatus ::= SEQUENCE { 
   wheelBrakes        BrakeAppliedStatus,
   traction           TractionControlStatus,
   abs                AntiLockBrakeStatus, 
   scs                StabilityControlStatus,
   brakeBoost         BrakeBoostApplied, 
   auxBrakes          AuxiliaryBrakeStatus
   }

Offset-B10 ::= INTEGER (-512..511)

SpeedProfileMeasurementList ::= SEQUENCE (SIZE(1..20)) OF SpeedProfileMeasurement

VehicleSize ::= SEQUENCE {
   width     VehicleWidth,
   length    VehicleLength
   }

EventDescription ::= SEQUENCE {
   typeEvent     ITIScodes,
   description   SEQUENCE (SIZE(1..8)) OF ITIScodes OPTIONAL,
   priority      Priority OPTIONAL,  
   heading       HeadingSlice  OPTIONAL,       
   extent        Extent OPTIONAL,  
   regional      SEQUENCE (SIZE(1..4)) OF 
                 RegionalExtension {{Reg-EventDescription}} OPTIONAL
   }

EssPrecipSituation ::= ENUMERATED {
   other (1), 
   unknown (2), 
   noPrecipitation (3), 
   unidentifiedSlight (4), 
   unidentifiedModerate (5), 
   unidentifiedHeavy (6), 
   snowSlight (7), 
   snowModerate (8), 
   snowHeavy (9), 
   rainSlight (10), 
   rainModerate (11), 
   rainHeavy (12), 
   frozenPrecipitationSlight (13), 
   frozenPrecipitationModerate (14), 
   frozenPrecipitationHeavy (15)
   }

GNSSstatus ::= BIT STRING {
   unavailable               (0), 
   isHealthy                 (1),
   isMonitored               (2),
   baseStationType           (3), 
   aPDOPofUnder5             (4), 
   inViewOfUnder5            (5), 
   localCorrectionsPresent   (6), 
   networkCorrectionsPresent (7)  
   } (SIZE(8))

TrailerWeight ::= INTEGER (0..64255)

WiperStatus ::= ENUMERATED {
     unavailable         (0), 
     off                 (1),  
     intermittent        (2), 
     low                 (3),
     high                (4),
     washerInUse         (5), 
     automaticPresent    (6) 
     }

AccelerationSet4Way ::= SEQUENCE {
   long Acceleration,          
   lat  Acceleration,          
   vert VerticalAcceleration,  
   yaw  YawRate
}

BrakeAppliedStatus ::= BIT STRING {
   unavailable (0),  
   leftFront   (1),  
   leftRear    (2),  
   rightFront  (3),  
   rightRear   (4)   
   } (SIZE (5))

PrivilegedEvents ::= SEQUENCE {
   sspRights   SSPindex,  
   event  PrivilegedEventFlags
   }

PathPrediction ::= SEQUENCE {
   radiusOfCurve RadiusOfCurvature, 
   confidence    Confidence 
   }

BSMcoreData ::= SEQUENCE {   
   msgCnt        MsgCount,  
   id            TemporaryID,
   secMark       DSecond,
   lat           Latitude,              
   long          Longitude,             
   elev          Elevation,             
   accuracy      PositionalAccuracy,    
   transmission  TransmissionState,
   speed         Speed,
   heading       Heading,               
   angle         SteeringWheelAngle,    
   accelSet      AccelerationSet4Way,   
   brakes        BrakeSystemStatus,     
   size          VehicleSize          
   }

MultiVehicleResponse ::= ENUMERATED {
     unavailable   (0), 
     singleVehicle (1),  
     multiVehicle  (2),  
     reserved      (3)  
     }

VehicleEventFlags ::= BIT STRING {
   eventHazardLights               (0),
   eventStopLineViolation          (1), 
   eventABSactivated               (2),
   eventTractionControlLoss        (3),
   eventStabilityControlactivated  (4),
   eventHazardousMaterials         (5),
   eventReserved1                  (6),   
   eventHardBraking                (7),
   eventLightsChanged              (8),
   eventWipersChanged              (9),
   eventFlatTire                   (10),
   eventDisabledVehicle            (11), 
   eventAirBagDeployment           (12)
   } (SIZE (13, ...))

RTCMPackage ::= SEQUENCE {  
   rtcmHeader  RTCMheader OPTIONAL,  
   msgs        RTCMmessageList
   }

ResponseType ::= ENUMERATED {
   notInUseOrNotEquipped      (0),            
   emergency                  (1),  
   nonEmergency               (2),  
   pursuit                    (3),  
   stationary                 (4),  
   slowMoving                 (5),  
   stopAndGoMovement          (6)  
   } 

SupplementalVehicleExtensions ::= SEQUENCE {
   classification   BasicVehicleClass        OPTIONAL,
   classDetails     VehicleClassification    OPTIONAL,
   vehicleData      VehicleData              OPTIONAL,
   weatherReport    WeatherReport            OPTIONAL, 
   weatherProbe     WeatherProbe             OPTIONAL, 
   obstacle         ObstacleDetection        OPTIONAL,
   status           DisabledVehicle          OPTIONAL,
   speedProfile     SpeedProfile             OPTIONAL, 
   theRTCM          RTCMPackage              OPTIONAL, 
   regional  SEQUENCE (SIZE(1..4)) OF 
             RegionalExtension {{Reg-SupplementalVehicleExtensions}} OPTIONAL
   }

Extent ::= ENUMERATED {
   useInstantlyOnly     (0),
   useFor3meters        (1),
   useFor10meters       (2),
   useFor50meters       (3),
   useFor100meters      (4),
   useFor500meters      (5),
   useFor1000meters     (6),
   useFor5000meters     (7),
   useFor10000meters    (8),
   useFor50000meters    (9),
   useFor100000meters   (10),
   useFor500000meters   (11),
   useFor1000000meters  (12),
   useFor5000000meters  (13),
   useFor10000000meters (14),
   forever              (15)  
   }  

BumperHeight ::= INTEGER (0..127) 



TrailerHistoryPointList ::= SEQUENCE (SIZE(1..23)) OF TrailerHistoryPoint

Reg-EventDescription      REG-EXT-ID-AND-TYPE ::= { ...  }

Velocity ::= INTEGER (0..8191) 

SpeedandHeadingandThrottleConfidence ::= SEQUENCE {
   heading   HeadingConfidence,    
   speed     SpeedConfidence,      
   throttle  ThrottleConfidence    
   }

WeatherReport ::= SEQUENCE {    
   isRaining        EssPrecipYesNo,
   rainRate         EssPrecipRate       OPTIONAL,
   precipSituation  EssPrecipSituation  OPTIONAL,
   solarRadiation   EssSolarRadiation   OPTIONAL,
   friction         EssMobileFriction   OPTIONAL,
   roadFriction     CoefficientOfFriction     OPTIONAL   
   }

RegionalExtension {REG-EXT-ID-AND-TYPE : Set} ::= SEQUENCE {
   regionId     REG-EXT-ID-AND-TYPE.&id( {Set} ),
   regExtValue  REG-EXT-ID-AND-TYPE.&Type( {Set}{@regionId} )
   }

SpeedProfile ::= SEQUENCE {
   speedReports SpeedProfileMeasurementList  
   }

BrakeBoostApplied ::= ENUMERATED {
   unavailable   (0), 
   off           (1), 
   on            (2)  
   }

VehicleData ::= SEQUENCE {    
   height        VehicleHeight   OPTIONAL,
   bumpers       BumperHeights   OPTIONAL,
   mass          VehicleMass     OPTIONAL,
   trailerWeight TrailerWeight   OPTIONAL
   }

PivotPointDescription ::= SEQUENCE {
   pivotOffset  Offset-B11,   
   pivotAngle   Angle,
   pivots       PivotingAllowed
   }

DMonth ::= INTEGER (0..12) 

DDay ::= INTEGER (0..31)  

HeadingConfidence ::= ENUMERATED {
   unavailable   (0), 
   prec10deg     (1), 
   prec05deg     (2), 
   prec01deg     (3), 
   prec0-1deg    (4), 
   prec0-05deg   (5), 
   prec0-01deg   (6), 
   prec0-0125deg (7)  
   }  

TrailerHistoryPoint ::= SEQUENCE {
   pivotAngle       Angle,
   timeOffset       TimeOffset,
   positionOffset   Node-XY-24b, 
   elevationOffset  VertOffset-B07 OPTIONAL,   
   heading          CoarseHeading OPTIONAL 
   }

AntennaOffsetSet ::= SEQUENCE { 
   antOffsetX  Offset-B12, 
   antOffsetY  Offset-B09, 
   antOffsetZ  Offset-B10  
   }

Speed ::= INTEGER (0..8191) 

Offset-B11 ::= INTEGER (-1024..1023)

Reg-BasicSafetyMessage     REG-EXT-ID-AND-TYPE ::= { ... }

ResponderGroupAffected ::= ENUMERATED { 
   emergency-vehicle-units           (9729),  
   federal-law-enforcement-units     (9730),  
   state-police-units                (9731),  
   county-police-units               (9732),  
   local-police-units                (9733),  
   ambulance-units                   (9734),  
   rescue-units                      (9735),  
   fire-units                        (9736),  
   hAZMAT-units                      (9737),  
   light-tow-unit                    (9738),  
   heavy-tow-unit                    (9739),  
   freeway-service-patrols           (9740),  
   transportation-response-units     (9741),  
   private-contractor-response-units (9742)  
   }

PositionalAccuracy ::= SEQUENCE {
   semiMajor     SemiMajorAxisAccuracy,
   semiMinor     SemiMinorAxisAccuracy,
   orientation   SemiMajorAxisOrientation
   }

FuelType ::= INTEGER (0..15)

FullPositionVector ::= SEQUENCE {
   utcTime             DDateTime OPTIONAL,   
   long                Longitude,            
   lat                 Latitude,             
   elevation           Elevation  OPTIONAL,  
   heading             Heading OPTIONAL, 
   speed               TransmissionAndSpeed OPTIONAL,
   posAccuracy         PositionalAccuracy OPTIONAL,
   timeConfidence      TimeConfidence OPTIONAL,
   posConfidence       PositionConfidenceSet OPTIONAL,
   speedConfidence     SpeedandHeadingandThrottleConfidence OPTIONAL 
   }

BasicVehicleRole ::= ENUMERATED {
    basicVehicle     (0), 
    publicTransport  (1), 
    specialTransport (2), 
    dangerousGoods   (3), 
    roadWork         (4), 
    roadRescue       (5), 
    emergency        (6), 
    safetyCar        (7), 
    none-unknown     (8), 
    truck            (9), 
    motorcycle      (10), 
    roadSideSource  (11), 
    police          (12), 
    fire            (13), 
    ambulance       (14), 
    dot             (15), 
    transit         (16), 
    slowMoving      (17), 
    stopNgo         (18), 
    cyclist         (19), 
    pedestrian      (20), 
    nonMotorized    (21), 
    military        (22) 
    }  

DDateTime ::= SEQUENCE {
   year    DYear    OPTIONAL,    
   month   DMonth   OPTIONAL,   
   day     DDay     OPTIONAL,  
   hour    DHour    OPTIONAL,   
   minute  DMinute  OPTIONAL,  
   second  DSecond  OPTIONAL,  
   offset  DOffset  OPTIONAL 
   }

SpeedProfileMeasurement ::= GrossSpeed 

DHour ::= INTEGER (0..31) 

VehicleHeight ::= INTEGER (0..127) 

TimeConfidence ::= ENUMERATED {
   unavailable              (0), 
   time-100-000             (1), 
   time-050-000             (2), 
   time-020-000             (3), 
   time-010-000             (4), 
   time-002-000             (5), 
   time-001-000             (6), 
   time-000-500             (7), 
   time-000-200             (8), 
   time-000-100             (9), 
   time-000-050            (10), 
   time-000-020            (11), 
   time-000-010            (12), 
   time-000-005            (13), 
   time-000-002            (14), 
   time-000-001            (15), 
   time-000-000-5          (16), 
   time-000-000-2          (17), 
   time-000-000-1          (18), 
   time-000-000-05         (19), 
   time-000-000-02         (20), 
   time-000-000-01         (21), 
   time-000-000-005        (22), 
   time-000-000-002        (23), 
   time-000-000-001        (24), 
   time-000-000-000-5      (25), 
   time-000-000-000-2      (26), 
   time-000-000-000-1      (27), 
   time-000-000-000-05     (28), 
   time-000-000-000-02     (29), 
   time-000-000-000-01     (30), 
   time-000-000-000-005    (31), 
   time-000-000-000-002    (32), 
   time-000-000-000-001    (33), 
   time-000-000-000-000-5  (34), 
   time-000-000-000-000-2  (35), 
   time-000-000-000-000-1  (36), 
   time-000-000-000-000-05 (37), 
   time-000-000-000-000-02 (38), 
   time-000-000-000-000-01 (39)  
   }

CoefficientOfFriction ::= INTEGER (0..50) 



AmbientAirTemperature ::= INTEGER (0..191) 

StabilityControlStatus ::= ENUMERATED {
   unavailable (0), 
   off         (1), 
   on          (2), 
   engaged     (3)  
   }

WiperRate ::= INTEGER (0..127) 

VehicleType ::= ENUMERATED {
   none                 (0),  
   unknown              (1),  
   special              (2),  
   moto                 (3),  
   car                  (4),  
   carOther             (5),  
   bus                  (6),  
   axleCnt2             (7),  
   axleCnt3             (8),  
   axleCnt4             (9),  
   axleCnt4Trailer      (10), 
   axleCnt5Trailer      (11), 
   axleCnt6Trailer      (12), 
   axleCnt5MultiTrailer (13), 
   axleCnt6MultiTrailer (14), 
   axleCnt7MultiTrailer (15)  
   } 

Latitude ::= INTEGER (-900000000..900000001)  

TimeOffset ::= INTEGER (1..65535)

OffsetLL-B18 ::= INTEGER (-131072..131071)     

RadiusOfCurvature ::= INTEGER (-32767..32767)

VerticalAccelerationThreshold ::= BIT STRING {
   notEquipped (0), 
   leftFront   (1), 
   leftRear    (2), 
   rightFront  (3), 
   rightRear   (4)  
   } (SIZE(5))



VerticalAcceleration ::= INTEGER (-127..127) 

TrailerUnitDescriptionList ::= SEQUENCE (SIZE(1..8)) OF TrailerUnitDescription

LightbarInUse ::= ENUMERATED {
     unavailable         (0),  
     notInUse            (1),  
     inUse               (2),  
     yellowCautionLights (3),  
     schooldBusLights    (4),  
     arrowSignsActive    (5),  
     slowMovingVehicle   (6),   
     freqStops           (7)   
     }

VehicleGroupAffected ::= ENUMERATED { 
   all-vehicles                               (9217),  
   bicycles                                   (9218),  
   motorcycles                                (9219),  
   cars                                       (9220),  
   light-vehicles                             (9221),  
   cars-and-light-vehicles                    (9222),  
   cars-with-trailers                         (9223),  
   cars-with-recreational-trailers            (9224),  
   vehicles-with-trailers                     (9225),  
   heavy-vehicles                             (9226),  
   trucks                                     (9227),  
   buses                                      (9228),  
   articulated-buses                          (9229),  
   school-buses                               (9230),  
   vehicles-with-semi-trailers                (9231),  
   vehicles-with-double-trailers              (9232),  
   high-profile-vehicles                      (9233),  
   wide-vehicles                              (9234),  
   long-vehicles                              (9235),  
   hazardous-loads                            (9236),  
   exceptional-loads                          (9237),  
   abnormal-loads                             (9238),  
   convoys                                    (9239),  
   maintenance-vehicles                       (9240),  
   delivery-vehicles                          (9241),  
   vehicles-with-even-numbered-license-plates (9242),  
   vehicles-with-odd-numbered-license-plates  (9243),  
   vehicles-with-parking-permits              (9244),  
   vehicles-with-catalytic-converters         (9245),  
   vehicles-without-catalytic-converters      (9246),  
   gas-powered-vehicles                       (9247),  
   diesel-powered-vehicles                    (9248),  
   lPG-vehicles                               (9249),  
   military-convoys                           (9250),  
   military-vehicles                          (9251)  
   }

WeatherProbe ::= SEQUENCE {
   airTemp      AmbientAirTemperature  OPTIONAL,
   airPressure  AmbientAirPressure     OPTIONAL,
   rainRates    WiperSet               OPTIONAL
   }

RTCMmessageList ::= SEQUENCE (SIZE(1..5)) OF RTCMmessage

DYear ::= INTEGER (0..4095) 

EssPrecipRate ::= INTEGER (0..65535) 

RTCMheader ::= SEQUENCE {
   status     GNSSstatus,
   offsetSet  AntennaOffsetSet
   }

Offset-B09 ::= INTEGER (-256..255)

PrivilegedEventFlags ::= BIT STRING {
   peUnavailable                (0), 
   peEmergencyResponse          (1),
   peEmergencyLightsActive      (2),
   peEmergencySoundActive       (3),
   peNonEmergencyLightsActive   (4),
   peNonEmergencySoundActive    (5)
   } (SIZE (16))

TransmissionAndSpeed ::= SEQUENCE {
   transmisson   TransmissionState,
   speed         Velocity
   }

Priority ::= OCTET STRING (SIZE(1)) 

BumperHeights ::= SEQUENCE {
   front      BumperHeight, 
   rear       BumperHeight
   }

Heading ::= INTEGER (0..28800) 

ExteriorLights ::= BIT STRING { 
   lowBeamHeadlightsOn       (0), 
   highBeamHeadlightsOn      (1), 
   leftTurnSignalOn          (2), 
   rightTurnSignalOn         (3), 
   hazardSignalOn            (4), 
   automaticLightControlOn   (5),
   daytimeRunningLightsOn    (6), 
   fogLightOn                (7), 
   parkingLightsOn           (8) 
   } (SIZE (9, ...))

IncidentResponseEquipment ::= ENUMERATED { 
   ground-fire-suppression          (9985),   
   heavy-ground-equipment           (9986),   
   aircraft                         (9988),   
   marine-equipment                 (9989),   
   support-equipment                (9990),   
   medical-rescue-unit              (9991),   
   other                            (9993),   
   ground-fire-suppression-other    (9994),   
   engine                           (9995),   
   truck-or-aerial                  (9996),   
   quint                            (9997),   
   tanker-pumper-combination        (9998),   
   brush-truck                      (10000),  
   aircraft-rescue-firefighting     (10001),  
   heavy-ground-equipment-other     (10004),  
   dozer-or-plow                    (10005),  
   tractor                          (10006),  
   tanker-or-tender                 (10008),  
   aircraft-other                   (10024),  
   aircraft-fixed-wing-tanker       (10025),  
   helitanker                       (10026),  
   helicopter                       (10027),  
   marine-equipment-other           (10034),  
   fire-boat-with-pump              (10035),  
   boat-no-pump                     (10036),  
   support-apparatus-other          (10044),  
   breathing-apparatus-support      (10045),  
   light-and-air-unit               (10046),  
   medical-rescue-unit-other        (10054),  
   rescue-unit                      (10055),  
   urban-search-rescue-unit         (10056),  
   high-angle-rescue                (10057),  
   crash-fire-rescue                (10058),  
   bLS-unit                         (10059),  
   aLS-unit                         (10060),  
   mobile-command-post              (10075),  
   chief-officer-car                (10076),  
   hAZMAT-unit                      (10077),  
   type-i-hand-crew                 (10078),  
   type-ii-hand-crew                (10079),  
   privately-owned-vehicle          (10083),  
   other-apparatus-resource         (10084),  
   ambulance                        (10085),  
   bomb-squad-van                   (10086),  
   combine-harvester                (10087),  
   construction-vehicle             (10088),  
   farm-tractor                     (10089),  
   grass-cutting-machines           (10090),  
   hAZMAT-containment-tow           (10091),  
   heavy-tow                        (10092),  
   light-tow                        (10094),  
   flatbed-tow                      (10114), 
   hedge-cutting-machines           (10093),  
   mobile-crane                     (10095),  
   refuse-collection-vehicle        (10096),  
   resurfacing-vehicle              (10097),  
   road-sweeper                     (10098),  
   roadside-litter-collection-crews (10099),  
   salvage-vehicle                  (10100),  
   sand-truck                       (10101),  
   snowplow                         (10102),  
   steam-roller                     (10103),  
   swat-team-van                    (10104),  
   track-laying-vehicle             (10105),  
   unknown-vehicle                  (10106),  
   white-lining-vehicle             (10107),  
   dump-truck                       (10108),  
   supervisor-vehicle               (10109),  
   snow-blower                      (10110),  
   rotary-snow-blower               (10111),  
   road-grader                      (10112),  
   steam-truck                      (10113)  
   }

VehicleWidth ::= INTEGER (0..1023) 

GenericLocations ::= ENUMERATED  { 
   on-bridges                  (7937),  
   in-tunnels                  (7938),  
   entering-or-leaving-tunnels (7939),  
   on-ramps                    (7940),  
   in-road-construction-area   (7941),  
   around-a-curve              (7942),  
   on-curve                    (8026),   
   on-tracks                   (8009),   
   in-street                   (8025),  
   shoulder                    (8027),   
   on-minor-roads              (7943),  
   in-the-opposing-lanes       (7944),  
   adjacent-to-roadway         (7945),  
   across-tracks               (8024),   
   on-bend                     (7946),  
   intersection                (8032),   
   entire-intersection         (7947),  
   in-the-median               (7948),  
   moved-to-side-of-road       (7949),  
   moved-to-shoulder           (7950),  
   on-the-roadway              (7951),  
   dip                         (8010),   
   traffic-circle              (8011),  
   crossover                   (8028),  
   cross-road                  (8029),  
   side-road                   (8030),  
   to                          (8014),   
   by                          (8015),   
   through                     (8016),   
   area-of                     (8017),  
   under                       (8018),     
   over                        (8019),   
   from                        (8020),   
   approaching                 (8021),   
   entering-at                 (8022),  
   exiting-at                  (8023),  
   in-shaded-areas             (7952),  
   in-low-lying-areas          (7953),  
   in-the-downtown-area        (7954),  
   in-the-inner-city-area      (7955),  
   in-parts                    (7956),  
   in-some-places              (7957),  
   in-the-ditch                (7958),  
   in-the-valley               (7959),  
   on-hill-top                 (7960),  
   near-the-foothills          (7961),  
   at-high-altitudes           (7962),  
   near-the-lake               (7963),  
   near-the-shore              (7964),  
   nearby-basin                (8008),  
   over-the-crest-of-a-hill    (7965),  
   other-than-on-the-roadway   (7966),  
   near-the-beach              (7967),  
   near-beach-access-point     (7968),  
   mountain-pass               (8006),  
   lower-level                 (7969),  
   upper-level                 (7970),  
   airport                     (7971),  
   concourse                   (7972),  
   gate                        (7973),  
   baggage-claim               (7974),  
   customs-point               (7975),  
   reservation-center          (8007),  
   station                     (7976),  
   platform                    (7977),  
   dock                        (7978),  
   depot                       (7979),  
   ev-charging-point           (7980),  
   information-welcome-point   (7981),  
   at-rest-area                (7982),  
   at-service-area             (7983),  
   at-weigh-station            (7984),  
   roadside-park               (8033),  
   picnic-areas                (7985),  
   rest-area                   (7986),  
   service-stations            (7987),  
   toilets                     (7988),  
   bus-stop                    (8031),  
   park-and-ride-lot           (8012),  
   on-the-right                (7989),  
   on-the-left                 (7990),  
   in-the-center               (7991),  
   in-the-opposite-direction   (7992),  
   cross-traffic               (7993),  
   northbound-traffic          (7994),  
   eastbound-traffic           (7995),  
   southbound-traffic          (7996),  
   westbound-traffic           (7997),  
   north                       (7998),  
   south                       (7999),  
   east                        (8000),  
   west                        (8001),  
   northeast                   (8002),  
   northwest                   (8003),  
   southeast                   (8004),  
   southwest                   (8005)  
   }

ObstacleDistance ::= INTEGER (0..32767) 

END
