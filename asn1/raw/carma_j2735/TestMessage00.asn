TestMessage00 DEFINITIONS AUTOMATIC TAGS ::= BEGIN



TestMessage00 ::= SEQUENCE {
   header          MobilityHeader,
   body            MobilityRequest
   }

MobilityRequest ::= SEQUENCE {
   strategy        MobilityStrategy,
   planType        MobilityPlanType,
   urgency         MobilityUrgency,
   location        MobilityLocation,
   strategyParams  MobilityParameters,
   trajectoryStart MobilityLocation OPTIONAL,
   trajectory      MobilityLocationOffsets OPTIONAL,
   expiration      MobilityTimestamp OPTIONAL
}

MobilityTimestamp ::= IA5String (SIZE(19))

MobilityECEFOffset ::= SEQUENCE {
   offsetX         MobilityECEFOffsetCoordinate,
   offsetY         MobilityECEFOffsetCoordinate,
   offsetZ         MobilityECEFOffsetCoordinate
}

MobilityECEFCoordinate ::= INTEGER(-638363700..638363700)

MobilityLocationOffsets ::= SEQUENCE (SIZE(0..60)) OF MobilityECEFOffset

MobilityParameters ::= IA5String (SIZE(2..1000))

MobilityECEFOffsetCoordinate ::= INTEGER(-500..501)

MobilityUrgency ::= INTEGER (0..1000)

MobilityLocation ::= SEQUENCE {
   ecefX           MobilityECEFCoordinate,
   ecefY           MobilityECEFCoordinate,
   ecefZ           MobilityECEFCoordinate,
   timestamp       MobilityTimestamp
}

MobilityStaticID ::= IA5String (SIZE(2..16))

MobilityStrategy ::= IA5String (SIZE(2..50))

MobilityPlanType ::= ENUMERATED {
   unknown (0), 
   changingLanesToTheLeft (1), 
   changingLanesToTheRight (2), 
   joinPlatoonAtRear (3),
   platoonFollowerJoin (4)
   }

MobilityGUID ::= IA5String (SIZE(36))

MobilityHeader ::= SEQUENCE {
   hostStaticId    MobilityStaticID,
   targetStaticId  MobilityStaticID,
   hostBSMId       MobilityDynamicID,
   planId          MobilityGUID,
   timestamp       MobilityTimestamp
}

MobilityDynamicID ::= IA5String (SIZE(8))

END
