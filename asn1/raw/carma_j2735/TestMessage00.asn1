TestMessage00 DEFINITIONS AUTOMATIC TAGS ::= BEGIN

MessageFrame ::= SEQUENCE {
   messageId   MESSAGE-ID-AND-TYPE.&id({MessageTypes}),
   value       MESSAGE-ID-AND-TYPE.&Type({MessageTypes}{@.messageId}),
   ...
   }

MESSAGE-ID-AND-TYPE ::= CLASS {
   &id    DSRCmsgID UNIQUE,
   &Type 
   } WITH SYNTAX {&Type IDENTIFIED BY &id}

MessageTypes MESSAGE-ID-AND-TYPE ::= {  
{ TestMessage00 IDENTIFIED BY testMessage00 }
}

DSRCmsgID ::= INTEGER (0..32767)

   testMessage00                     DSRCmsgID ::=  240 -- Hex 0xF0 

TestMessage00 ::= SEQUENCE {
   -- TestMessage00 is only for MobilityRequest message
   header          MobilityHeader,
   body            MobilityRequest,
   ...
   }
MobilityECEFOffsetCoordinate ::= INTEGER(-500..501)
   -- offset in X, Y, Z coordinates in ECEF frame
   -- LSB units are 1 cm
   -- a value of 501 means unavaliable

MobilityECEFOffset ::= SEQUENCE {
   offsetX         MobilityECEFOffsetCoordinate,
   offsetY         MobilityECEFOffsetCoordinate,
   offsetZ         MobilityECEFOffsetCoordinate
}

MobilityUrgency ::= INTEGER (0..1000)
   -- a value of 0 shall be used for unknown
   -- a value of 1000 shall be used for the highest urgency

MobilityGUID ::= IA5String (SIZE(36))
   -- the unique ID for different plan/strategy events
   -- in Java UUID format xxxxxxxx-xxxx-xxxx-xxxx-xxxxxxxxxxxx

MobilityStrategy ::= IA5String (SIZE(2..50))
   -- the desired strategy to handle this message
   -- "[]" means not defined

MobilityDynamicID ::= IA5String (SIZE(8))
   -- mobility dynamic ID is the same as host vehicle current BSM ID in hex string

MobilityTimestamp ::= IA5String (SIZE(19))
   -- UNIX timestamp in milliseconds in string, which indicates the time elapsed since UNIX epoch
   -- the maximum value is the MAX_VALUE of Java Long type (which is in length 19)

MobilityPlanType ::= ENUMERATED {
   unknown (0), 
   changingLanesToTheLeft (1), 
   changingLanesToTheRight (2), 
   joinPlatoonAtRear (3),
   platoonFollowerJoin (4),
   ...
   }

MobilityLocation ::= SEQUENCE {
   ecefX           MobilityECEFCoordinate,
   ecefY           MobilityECEFCoordinate,
   ecefZ           MobilityECEFCoordinate,
   timestamp       MobilityTimestamp
}

MobilityStaticID ::= IA5String (SIZE(2..16))
   -- the license plate number for each vehicle
   -- "[]" indicates ID is not specified

MobilityRequest ::= SEQUENCE {
   strategy        MobilityStrategy,
   planType        MobilityPlanType,
   urgency         MobilityUrgency,
   location        MobilityLocation,
   strategyParams  MobilityParameters,
   trajectoryStart MobilityLocation OPTIONAL,
   trajectory      MobilityLocationOffsets OPTIONAL,
   expiration      MobilityTimestamp OPTIONAL
}

MobilityParameters ::= IA5String (SIZE(2..1000))
   -- the content of this string is defined by each plugin

MobilityLocationOffsets ::= SEQUENCE (SIZE(0..60)) OF MobilityECEFOffset

MobilityECEFCoordinate ::= INTEGER(-638363700..638363700)
   -- X, Y, Z coordinates in ECEF frame
   -- LSB units are 1 cm
   -- a value of 0 means unavaliable

MobilityHeader ::= SEQUENCE {
   hostStaticId    MobilityStaticID,
   targetStaticId  MobilityStaticID,
   hostBSMId       MobilityDynamicID,
   planId          MobilityGUID,
   timestamp       MobilityTimestamp
}

END
